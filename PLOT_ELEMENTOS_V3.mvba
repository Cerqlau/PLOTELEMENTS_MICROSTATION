Attribute VB_Name = "Elementos"
Public Sub Copia_elementos(Elementos As Element)
    
    
'------------------------------------------------------------------------------------------------------------------------------------------
'                                                           INFORMAÇÕES
'------------------------------------------------------------------------------------------------------------------------------------------

'Código para plotar e manipular elementos no microstation a partir de uma base de dados no excel
'criado por Lauro Cerqueira
    
'------------------------------------------------------------------------------------------------------------------------------------------
'                                                           DECLARAÇÃO DE VARIÁVEIS
'------------------------------------------------------------------------------------------------------------------------------------------
     
    
    'Tratamento de Erro
    On Error GoTo Error
    
    'Declaração de variáveis globais para leitura do database na planilha Excel
    Dim excelApp As Excel.Application 'Criação de aplicação do excel
    Dim mySheet As Worksheet 'Criação de um objeto planilha
    Dim X As Long 'coordenadas East
    Dim Y As Long 'coordenadas North
    Dim Array_X() As Long, Array_Y() As Long, Array_Z() As Long 'Arrays para armazenamento dos pontos X,Y,Z
    Dim Qt_X As Integer, Qt_Y As Integer, Qt_Z As Integer 'quantidade de pontos X,Y,Z
    Set excelApp = CreateObject("Excel.Application") 'instancia de um objeto da aplicação excel
    
    'Declaração Variáveis Globais para manipulação do elemento  no Microstation
    Dim elemento As Element 'Elemento
    Dim Copia As Element
    Dim elemento_enum As ElementEnumerator
    Dim Origem As Point3d 'elemento coordenadas X,Y,Z Origem
    Dim Destino As Point3d 'elemento coordenadas X,Y,Z Destino
    Dim mytext As TextElement 'Elemento Texto
    Dim textpt As Point3d 'Coordenada Elemento Texto
    Dim rotMatrix As Matrix3d 'Matriz 3d
    
'------------------------------------------------------------------------------------------------------------------------------------------
'                                                           MANIPULAÇÃO DA PLANILA DE DADOS
'------------------------------------------------------------------------------------------------------------------------------------------
    
    'Se atribuir True, a janela do Excel aparecerá
    'excelApp.Visible = True
    excelApp.Visible = False
    
    excelApp.Workbooks.Open (Path)
    'Debug.Print excelApp.ActiveWorkbook.Name
    Set mySheet = excelApp.ActiveWorkbook.Worksheets("Sheet1") 'instancia da planilha específica
    mySheet.Activate
    
    'Verificação da quantidade de pontos por linha
    Qt_X = mySheet.Cells(1, 1).End(xlDown).Row 'Comando que simula Ctrl+shift+seta para baixo no excel
    Qt_Y = mySheet.Cells(1, 2).End(xlDown).Row
    Qt_Z = mySheet.Cells(1, 3).End(xlDown).Row
    
    'Redimensionamento de arrays
    ReDim Array_X(Qt_X - 1)
    ReDim Array_Y(Qt_Y - 1)
    ReDim Array_Z(Qt_Z - 1)
    
    'Captura de cordenadas X
    For i = 0 To (Qt_X - 1)
    Array_X(i) = mySheet.Cells(i + 1, 1).Value
    Next i
    
    'Captura de cordenadas Y
    For i = 0 To (Qt_Y - 1)
    Array_Y(i) = mySheet.Cells(i + 1, 2).Value
    Next i
    
    'Captura de profundiade Z
    For i = 0 To (Qt_Z - 1)
    Array_Z(i) = mySheet.Cells(i + 1, 3).Value
    Next i
  
    
    'Termina o Excel
    excelApp.Quit
    
'------------------------------------------------------------------------------------------------------------------------------------------
'                                                          MANIPULAÇÃO DO OBJETO SELECIONADO NO MICROSTATION
'------------------------------------------------------------------------------------------------------------------------------------------
    
    'MANIPULAÇÃO DO OBJETO SELECIONADO
        
    Set elemento = Elementos.AsCellElement
        
        If elemento.IsCellElement Then
                
            'Capturando coordenada da seleção
            
            Origem.X = elemento.AsCellElement.Origin.X
            Origem.Y = elemento.AsCellElement.Origin.Y
            Origem.Z = elemento.AsCellElement.Origin.Z
            
            ActiveModelReference.UnselectAllElements 'limpa a seleção
            ActiveModelReference.SelectElement elemento, True 'seleciona somente o objeto principal
            CadInputQueue.SendCommand "copy" 'Copiando o elemento para coodenada destino
            CadInputQueue.SendDataPoint Origem 'set de coordenada origem
            
            For i = 1 To (Qt_X - 1)
                'Inserindo coordenada destino e realizando a cópia
                Destino.X = Array_X(i)
                Destino.Y = Array_Y(i)
                Destino.Z = 0
                CadInputQueue.SendDataPoint Destino
            Next i
            CadInputQueue.SendReset
        End If
    
Saida:
'Limpando os comandos de seleção
CadInputQueue.SendReset
Exit Sub
    
Error:
MsgBox "Erros inexperado contate o desenvolvedor", vbCritical, "Error"
Exit Sub
    
End Sub

Attribute VB_Name = "Menu"
Public Sub Inicializar()

'Tratamento de Erro
On Error GoTo Error

Dim excelApp As Excel.Application 'Criação de aplicação do excel
Set excelApp = CreateObject("Excel.Application") 'instancia de um objeto da aplicação excel
Dim text As String
Dim Elemento0 As Element 'Elemento
Dim Elemento1 As Element 'Elemento
Dim Elemento2 As Element 'Elemento
Dim elemento_enum As ElementEnumerator
Dim Check As Integer

Inicio:

'------------------------------------------------------------------------------------------------------------------------------------------
'                                                          MANIPULAÇÃO DO OBJETO SELECIONADO NO MICROSTATION
'------------------------------------------------------------------------------------------------------------------------------------------
 
Check = 0
  
Set elemento_enum = ActiveModelReference.GetSelectedElements
    
    While elemento_enum.MoveNext
         
        Set Elemento0 = elemento_enum.Current
        
            If Elemento0.IsTextElement Then
                Set Elemento1 = elemento_enum.Current
               If Check = 0 Then
                  Check = 1
               Else
                  Check = 3
               End If
            ElseIf Elemento0.IsCellElement Then
                 Set Elemento2 = elemento_enum.Current
                If Check = 0 Then
                  Check = 2
               Else
                  Check = 3
              End If
            End If
    Wend
    

Select Case Check
Case 0
    MsgBox "Nenhum elemento selecioando" & Chr(13) & "Reinicie a aplicação e selecione os elementos", vbCritical
    Exit Sub
Case 1
    Profundidade Elemento1.AsTextElement
    MsgBox "Somente o elemento texto foi plotado", vbCritical
    Exit Sub
Case 2
    Copia_elementos Elemento2.AsCellElement
    MsgBox "Somente o elemento célula foi plotado", vbCritical
    Exit Sub
Case 3
    Copia_elementos Elemento2
    Profundidade Elemento1
    MsgBox "Ambos elementos foram plotados sucesso", vbOKOnly
    Exit Sub
End Select

Error:
CadInputQueue.SendReset
MsgBox "Erros inexperado contate o desenvolvedor", vbCritical, "Error"
Exit Sub

Sair:
MsgBox "Deixando aplicação", vbOKOnly
End Sub

Attribute VB_Name = "Start"
Private handler As eLocate 'necessário definir o manipulador de evento desta forma para evitar sua desintegração após execução da sub
Global Path As String

Sub main()
'------------------------------------------------------------------------------------------------------------------------------------------
'                                                           INFORMAÇÕES
'------------------------------------------------------------------------------------------------------------------------------------------

'Código para plotar e manipular elementos no microstation a partir de uma base de dados no excel
'criado por Lauro Cerqueira

Dim excelApp As Excel.Application 'Criação de aplicação do excel
Set excelApp = CreateObject("Excel.Application") 'instancia de um objeto da aplicação excel
Dim text As String
Dim Elemento0 As Element 'Elemento
Dim Elemento1 As Element 'Elemento
Dim Elemento2 As Element 'Elemento
Dim elemento_enum As ElementEnumerator
Dim Check As Integer

text = "                                INFORMAÇÃO" _
        & "" & Chr(13) & "--------------------------------------------------------------------------" _
        & "" & Chr(13) & "Esta aplicação foi criada com intuido de facilitar a plotagem de elementos no Microstation." _
        & "" & Chr(13) & "Para sua exceução deve-se possuir uma base de dados em planilha no excel que contenha a coluna A" _
        & " preenchida com as coordenadas Leste, B com as coordenadas Norte e C com profundidade." _
        & "" & Chr(13) & "--------------------------------------------------------------------------" _
        & "" & Chr(13) & "                          INSTRUÇÕES PARA USO" _
        & "" & Chr(13) & "--------------------------------------------------------------------------" _
        & "" & Chr(13) & "1 - Previamente Plote a primeiro elemento e texto de profundidade;" _
        & "" & Chr(13) & "2 - Ajuste cor, escala e camada;" _
        & "" & Chr(13) & "3 - Carregue a planilha base de dados;" _
        & "" & Chr(13) & "4 - Selecione o elemento e o texto;" _
        & "" & Chr(13) & "6 - Be Happy !!!   =]" _
        & "" & Chr(13) & "--------------------------------------------------------------------------" _
        & "" & Chr(13) & "Created By Lauro Cerqueira"
MsgBox text, vbQuestion 'Texto de informações iniciais


'------------------------------------------------------------------------------------------------------------------------------------------
'                                                           MANIPULAÇÃO DA PLANILA DE DADOS
'------------------------------------------------------------------------------------------------------------------------------------------


'Solicita escolha de base de dados
Caminho:

'Encontrar o arquivo
Set Objeto = CreateObject("scripting.filesystemobject")
Path = excelApp.GetOpenFilename(filefilter:="xlsx File, *.*")

'Verifica escolha do usuário e se o arquivo é válido
If Path = "" Or Path = "False" Then
    GoTo Sair
Else
    If Right(Path, 4) = "xlsx" Then
       GoTo Inicio
    Else
        MsgBox "Tipo de arquivo incorreto", vbCritical
        GoTo Caminho
    End If
End If

Sair:
MsgBox "Deixando aplicação", vbOKOnly
Exit Sub

Inicio:

'Chamada da clasee criada elocate e que utiliza as primitiva IlocateCommandEvents para interação de seleção com o usuário
Set handler = New eLocate
    CommandState.StartLocate handler
End Sub

Attribute VB_Name = "Texto"
Public Sub Profundidade(Elementos As Element)

'------------------------------------------------------------------------------------------------------------------------------------------
'                                                           INFORMAÇÕES
'------------------------------------------------------------------------------------------------------------------------------------------

'Código para plotar e manipular elementos no microstation a partir de uma base de dados no excel
'criado por Lauro Cerqueira

'------------------------------------------------------------------------------------------------------------------------------------------
'                                                           DECLARAÇÃO DE VARIÁVEIS
'------------------------------------------------------------------------------------------------------------------------------------------
    
'Tratamento de Erro
On Error GoTo Error

'Declaração de variáveis globais para leitura do database na planilha Excel
Dim excelApp As Excel.Application 'Criação de aplicação do excel
Dim mySheet As Worksheet 'Criação de um objeto planilha
Dim X As Long 'coordenadas East
Dim Y As Long 'coordenadas North
Dim Array_X() As Long, Array_Y() As Long, Array_Z() As Long 'Arrays para armazenamento dos pontos X,Y,Z
Dim Array_NX() As Long, Array_NY() As Long, Array_NZ() As Long 'Arrays para armazenamento dos pontos da profundiade X,Y,Z
Dim Qt_X As Integer, Qt_Y As Integer, Qt_Z As Integer 'quantidade de pontos X,Y,Z
Set excelApp = CreateObject("Excel.Application") 'instancia de um objeto da aplicação excel

'Declaração Variáveis Globais para manipulação do elemento  no Microstation
Dim elemento As Element 'Elemento
Dim Copia As TextElement 'Copiado
Dim elemento_enum As ElementEnumerator
Dim Origem As Point3d 'elemento coordenadas X,Y,Z Origem
Dim Destino As Point3d 'elemento coordenadas X,Y,Z Destino
      

'------------------------------------------------------------------------------------------------------------------------------------------
'                                                           MANIPULAÇÃO DA PLANILA DE DADOS
'------------------------------------------------------------------------------------------------------------------------------------------
Inicio:

'Atribuir True, a janela do Excel aparecerá
'excelApp.Visible = True
excelApp.Visible = False

excelApp.Workbooks.Open (Path) 'utiliza a aplicação excel para abrir o arquivo no caminho desejado
Set mySheet = excelApp.ActiveWorkbook.Worksheets("Sheet1") 'instancia da planilha específica
mySheet.Activate 'ativa a planilha específica para que as ações sejam executadas nela

'Verificação da quantidade de pontos por linha
Qt_X = mySheet.Cells(1, 1).End(xlDown).Row 'Comando que simula Ctrl+shift+seta para baixo no excel
Qt_Y = mySheet.Cells(1, 2).End(xlDown).Row
Qt_Z = mySheet.Cells(1, 3).End(xlDown).Row

'Redimensionamento de arrays
ReDim Array_X(Qt_X - 1)
ReDim Array_Y(Qt_Y - 1)
ReDim Array_Z(Qt_Z - 1)
ReDim Array_NX(Qt_X - 1)
ReDim Array_NY(Qt_Y - 1)
ReDim Array_NZ(Qt_Z - 1)

'Captura de cordenadas X
For i = 0 To (Qt_X - 1)
    Array_X(i) = mySheet.Cells(i + 1, 1).Value
Next i

'Captura de cordenadas Y
For i = 0 To (Qt_Y - 1)
    Array_Y(i) = mySheet.Cells(i + 1, 2).Value
Next i

'Captura de profundiade Z
For i = 0 To (Qt_Z - 1)
    Array_Z(i) = mySheet.Cells(i + 1, 3).Value
Next i

'Termina o Excel
excelApp.Quit
    
  

'------------------------------------------------------------------------------------------------------------------------------------------
'                                                          MANIPULAÇÃO DO OBJETO SELECIONADO NO MICROSTATION
'------------------------------------------------------------------------------------------------------------------------------------------
             
    Set elemento = Elementos.AsTextElement
        
        If elemento.IsTextElement Then
            
            'Capturando coordenada da seleção
            Origem.X = Round(Elementos.AsTextElement.AsTextElement.Origin.X, 0)
            Origem.Y = Round(Elementos.AsTextElement.AsTextElement.Origin.Y, 0)
            Origem.Z = Round(Elementos.AsTextElement.AsTextElement.Origin.Z, 0)
            
            'caclula o offset da do texto para o objeto batimetria
            Dif_X = Array_X(0) - Origem.X
            Dif_Y = Array_Y(0) - Origem.Y
            
            For i = 1 To (Qt_X - 1)
            
                'Cálculo coordenada destino texto
                Destino.Y = Array_Y(i) - Dif_Y
                Destino.X = Array_X(i) - Dif_X
                Destino.Z = 0
                
                'array de me para as coordenadas dos textos
                Array_NY(i) = Destino.Y
                Array_NX(i) = Destino.X
                Array_NZ(i) = Destino.Z
                
               'cópia do elemento
               Set Copia = ActiveModelReference.CopyElement(elemento)
               
               'edição do elemento texto
               With Copia.AsTextElement
               .Origin = Destino
               .text = Str(Array_Z(i))
               .Rewrite
               End With
            Next i
     End If
    
'Limpando os comandos de seleção
CadInputQueue.SendReset
Exit Sub


Error:
CadInputQueue.SendReset
MsgBox "Erros inexperado contate o desenvolvedor", vbCritical, "Error"
Exit Sub

Sair:

End Sub

Attribute VB_Name = "eLocate"
Attribute VB_Base = "0{FCFB3D2A-A0FA-1068-A738-08002B3371B5}"
Attribute VB_GlobalNameSpace = False
Attribute VB_Creatable = False
Attribute VB_PredeclaredId = False
Attribute VB_Exposed = False
Attribute VB_TemplateDerived = False
Attribute VB_Customizable = False
Implements ILocateCommandEvents
Private SelElement As Element
Private SelElement_enum As ElementEnumerator
Private cont As Integer
Private Sub ILocateCommandEvents_Accept(ByVal Element As Element, Point As Point3d, ByVal View As View)
'Evento responsável por interagir após dois clicks do mouse
'Vazio para que não haja ações durante o evento


End Sub
Private Sub ILocateCommandEvents_Cleanup()
'Evento responsável por limpar variáveis de classe
'Vazio para que não haja ações durante o evento
End Sub
Private Sub ILocateCommandEvents_Dynamics(Point As Point3d, ByVal View As View, ByVal DrawMode As MsdDrawingMode)
'Vazio para que não haja ações durante o evento
End Sub
Private Sub ILocateCommandEvents_LocateFailed()
'Evento responsável por interagir com usuário quando a seleção efetuada por este é realizada em área que não possuem objetos
'Vazio para que não haja ações durante o evento

End Sub
Private Sub ILocateCommandEvents_LocateFilter(ByVal Element As Element, Point As Point3d, Accepted As Boolean)
'Evento responsável por interagir com usuário após a seleção de elementos

Dim i As Integer
i = 0
ActiveModelReference.SelectElement Element, True
Set SelElement_enum = ActiveModelReference.GetSelectedElements
'informações na aba de log do Microstation
ShowCommand "Selecionar"
ShowPrompt "Click com o botão direito duas vezes para aceitar a seleção"
Accepet = False 'Opção false permite que a seleção seja efetuada sem a necessidade de duplo click
cont = cont + 1 'contador para limitar a quantidade de objetos selecionados

If cont = 2 Then
    verifica_elementos SelElement_enum
    Inicializar
End If


End Sub

Private Sub ILocateCommandEvents_LocateReset()
'Evento responsável por interagir com usuário quando o comando reset (botão direito do mouse) é ativado pelo usuário

If cont = 0 Then

    MsgBox "Nenhum elemento selecionado", vbOKOnly
    CommandState.StartDefaultCommand
    Verifica_Selecao = True
    Exit Sub

End If

verifica_elementos SelElement_enum

End Sub

Private Sub ILocateCommandEvents_Start()
'Evetento iniciado automaticamento ao iniciar a classe

MsgBox "Selecione texto e elemento", vbOKOnly
ShowCommand "Selecionar"
ShowPrompt "Selecione os elementos a serem localizados"
cont = 0
End Sub

Private Sub verifica_elementos(SelElement_enum_ As ElementEnumerator)
'Função responsável por realizar a verificação de quantidade e tipo de elementos selecionados
Dim elementtype As String
Dim SelElement_
Dim i As Integer
i = 0

While SelElement_enum_.MoveNext
    Set SelElement_ = SelElement_enum_.Current
    i = i + 1
    If SelElement_.IsCellElement Then
        elementtype = elementtype & "Célula" & ", "
    ElseIf SelElement_.IsTextElement Then
       elementtype = elementtype & "Texto" & ", "
    Else
       elementtype = elementtype & "Outro" & ", "
    End If
Wend




MsgBox "Elementos selecionados: " & i & Chr(13) & "Tipo de elemento: " & elementtype, vbOKOnly
CommandState.StartDefaultCommand
Verifica_Selecao = True

End Sub
